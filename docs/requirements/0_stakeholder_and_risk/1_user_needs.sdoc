[DOCUMENT]
TITLE: User Needs

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: TEXT
  FIELDS:
  - TITLE: UID
    TYPE: String
    REQUIRED: False
  - TITLE: STATEMENT
    TYPE: String
    REQUIRED: True
- TAG: USER_NEED
  PROPERTIES:
    PREFIX: UN-
    VIEW_STYLE: Narrative
  FIELDS:
  - TITLE: MID
    TYPE: String
    REQUIRED: False
  - TITLE: UID
    TYPE: String
    REQUIRED: True
  - TITLE: TITLE
    TYPE: String
    REQUIRED: True
  - TITLE: STATEMENT
    TYPE: String
    REQUIRED: True
  - TITLE: RATIONALE
    TYPE: String
    REQUIRED: False

[[SECTION]]
TITLE: Medication Scheduling

[USER_NEED]
UID: UN-101
TITLE: Schedule Management
STATEMENT: >>>
The Patient needs to program a simple daily medication schedule where medication is taken either once or twice a day, every day.
<<<
RATIONALE: >>>
"Simple" programming mode to ensure parity with device labeling. Labeling serves as risk mitigation factor.
<<<

[USER_NEED]
UID: UN-102
TITLE: Physical Loading
STATEMENT: >>>
The Patient needs to be able to easily load pills into the 14 distinct bins without spilling or mixing medications.
<<<

[USER_NEED]
UID: UN-103
TITLE: Medication Replenishment
STATEMENT: >>>
The Patient needs to transition the device from a completed (weekly, configurable) cycle to a new cycle to begin tracking the next cycle's doses.
<<<

[USER_NEED]
UID: UN-104
TITLE: Fill Confirmation
STATEMENT: >>>
The Patient needs to confirm to the system that medication has been physically loaded into the bins to reset the adherence tracking logic.
<<<

[USER_NEED]
UID: UN-105
TITLE: Mid-Cycle Adjustment
STATEMENT: >>>
The Patient needs to modify modify the medication schedule during an active cycle to accommodate immediate prescription changes without disrupting adherence tracking for medication already taken in the cycle.
<<<

[USER_NEED]
UID: UN-106
TITLE: Physical Label Alignment
STATEMENT: >>>
The Patient needs the digital medication schedule to strictly align with the physical labeling on the device (Day of Week and Sun/Moon symbols) to prevent confusion during dosing.
<<<
RATIONALE: >>>
Using the hardware labels as a primary safety safeguard reduces the risk of medication errors. If software prompts a dose, the physical label serves as a secondary verification for the Patient.
<<<

[USER_NEED]
UID: UN-107
TITLE: Chronological Bin Sequence
STATEMENT: >>>
The Patient needs the system to enforce that "Sun" (AM) bins are scheduled chronologically before "Moon" (PM) bins within the same calendar day.
<<<
RATIONALE: >>>
Prevents logical mapping errors where the digital schedule contradicts the intuitive physical layout of the device.
<<<

[[/SECTION]]

[[SECTION]]
TITLE: Daily Use

[USER_NEED]
UID: UN-201
TITLE: Visual Indicators
STATEMENT: >>>
The Patient needs clear visual cues on the physical device to signify medication needs to be taken and identify exactly which bin contains the current medication.
<<<

[USER_NEED]
UID: UN-202
TITLE: Remote Notification
STATEMENT: >>>
The Patient needs to receive a notification on their phone as a cue when medication is due to be taken.
<<<

[USER_NEED]
UID: UN-203
TITLE: Missed Dose Alerts
STATEMENT: >>>
The Patient needs to be alerted if a scheduled dose was not taken within a specified time window.
<<<

[USER_NEED]
UID: UN-204
TITLE: Notification Preference Control
STATEMENT: >>>
The user needs to choose which specific events (e.g., missed doses vs. upcoming doses) trigger notifications for themselves and their caregivers.
<<<

[USER_NEED]
UID: UN-205
TITLE: Battery Monitoring
STATEMENT: >>>
The Patient needs to be able to monitor the battery level of the device.
<<<

[USER_NEED]
UID: UN-206
TITLE: Critical Power Indication
STATEMENT: >>>
The Patient needs the system to provide distinct visual or digital alerts when the battery reaches a low or critical state.
<<<

[[/SECTION]]

[[SECTION]]
TITLE: Identity and Access Management

[USER_NEED]
UID: UN-301
TITLE: Patient Identity Creation
STATEMENT: >>>
The Patient needs to establish a unique, secure patient account capable of managing or monitoring one or more devices as the primary user.
<<<

[USER_NEED]
UID: UN-302
TITLE: Caregiver Identity Creation
STATEMENT: >>>
The Caregiver needs to establish a unique, secure account capable of managing or monitoring one or more devices used by the Patient.
<<<

[USER_NEED]
UID: UN-7312
TITLE: Account Name
STATEMENT: >>>
The Patient needs to see which Caregiver accounts have access to their device, and be able to determine which Caregiver such account belongs to.
<<<
RATIONALE: >>>
Need to present the user a name when listing account access so they know who each account belongs to.
<<<

[USER_NEED]
UID: UN-303
TITLE: Remote Monitoring Access
STATEMENT: >>>
The Caregiver needs to view the Patient's adherence and device status in real-time without the ability to modify the medication schedule.
<<<
RATIONALE: >>>
Ensures the Account Owner (Patient) is the sole authority for schedule modifications. This prevents remote clinicians or caregivers from altering dosing instructions, which is a key requirement for maintaining Class I regulatory status.
<<<

[USER_NEED]
UID: UN-304
TITLE: Remote Monitoring Revocation
STATEMENT: >>>
The Patient needs to revoke a Caregiver's ability to view adherence and device status.
<<<

[USER_NEED]
UID: UN-305
TITLE: Account Closure and Privacy
STATEMENT: >>>
The user needs to be able to close their account and have their personal identifying information removed while ensuring their historical health data remains available for research in an anonymous form.
<<<

[USER_NEED]
UID: UN-306
TITLE: User Login
STATEMENT: >>>
Existing users shall be able to authenticate securely to access their specific data views and device settings.
<<<

[USER_NEED]
UID: UN-307
TITLE: Schedule Modification Privilege
STATEMENT: >>>
The Patient needs the system to restrict medication and schedule modification permissions exclusively to their authenticated account.
<<<
RATIONALE: >>>
Prevents unauthorized or accidental schedule changes by secondary users (Caregivers/Researchers), mitigating the risk of dosing errors and race conditions.
<<<

[USER_NEED]
UID: UN-7311
TITLE: Record Access Control
STATEMENT: >>>
The Patient needs the system to ensure only authorized users are permitted to access or make changes to their data, records, and configuration.
<<<

[USER_NEED]
UID: UN-7314
TITLE: Patient Device List & Switch
STATEMENT: >>>
The Patient and the Caregiver need to know all the devices they posses or have access to, and be able to easily select and switch between such devices to access or make changes to their data, records, and configuration.
<<<

[[/SECTION]]

[[SECTION]]
TITLE: Adherence Monitoring and History

[USER_NEED]
UID: UN-401
TITLE: Automated Detection
STATEMENT: >>>
The Patient needs the system to automatically record a "taken" event when a scheduled bin is accessed during the correct time window.
<<<

[USER_NEED]
UID: UN-402
TITLE: Manual Correction
STATEMENT: >>>
The Patient needs to be able to manually modify the adherence record to correct false positives (opened bin but didn't take) or false negatives (took pill without device detecting).
<<<

[USER_NEED]
UID: UN-403
TITLE: Historical Visualization
STATEMENT: >>>
The user needs to view their medication adherence history over time (weekly or monthly).
<<<

[USER_NEED]
UID: UN-404
TITLE: Anomaly Context
STATEMENT: >>>
The user needs the system to differentiate between "Late" doses, "Missed" doses, and "On-Time" doses in the tracking record.
<<<

[USER_NEED]
UID: UN-405
TITLE: Data Integrity and Audit
STATEMENT: >>>
The user needs the system to maintain a complete and unalterable record of all device actions and medication events up to a specified retention period.
<<<

[USER_NEED]
UID: UN-406
TITLE: Connection Status Awareness
STATEMENT: >>>
The user needs to be notified if the device is no longer communicating with the service so they can rely on the physical device indicators instead of the app.
<<<

[USER_NEED]
UID: UN-407
TITLE: Data Synchronization
STATEMENT: >>>
The user needs their medication history to be automatically updated with any data collected while the device was offline once a connection is restored.
<<<

[[/SECTION]]

[[SECTION]]
TITLE: Provisioning and Onboarding

[USER_NEED]
UID: UN-501
TITLE: Device-Patient Association
STATEMENT: >>>
The Patient needs to securely pair the physical pill organizer to their account without technical expertise.
<<<

[USER_NEED]
UID: UN-502
TITLE: Device-Patient Dissociation
STATEMENT: >>>
The Patient needs to be able to dissociate their account from the physical device, revoking their access to make further schedule or configuration changes but preserving their adherence records and data.
<<<
RATIONALE: >>>
Need to make sure patient records are always preserved, but they are unable to make changes to the device (in case the device is given to someone else).
<<<

[USER_NEED]
UID: UN-503
TITLE: Proxy Technical Configuration
STATEMENT: >>>
The Caregiver needs to perform technical setup on behalf of a Patient without inheriting the permission to modify the medication schedule once the Patient account is linked.
<<<
RATIONALE: >>>
Maintains strict isolation between support (Caregiver) and ownership (Patient).
<<<

[USER_NEED]
UID: UN-504
TITLE: Device Handoff from Caregiver
STATEMENT: >>>
The Patient needs to be able to claim "primary ownership" of a device that was previously configured by a Caregiver, transferring the configured device to the Patient account.
<<<

[USER_NEED]
UID: UN-7313
TITLE: Physical Device Identification
STATEMENT: >>>
The Patient needs to be able to differentiate between multiple devices they may posses.
<<<
RATIONALE: >>>
Need to be able to see a device in the app and know which real-life device it refers to.
<<<

[USER_NEED]
UID: UN-7315
TITLE: Logical Device Identification
STATEMENT: >>>
The Patient needs the system to differentiate between multiple devices they may posses.
<<<
RATIONALE: >>>
The system needs a way to identify a unique device other than via the patient (they may own multiple).
<<<

[USER_NEED]
UID: UN-505
TITLE: Power Loss State Persistence
STATEMENT: >>>
The Patient needs the device to restore its previous state and operation automatically following a power loss, without requiring reconfiguration.
<<<

[USER_NEED]
UID: UN-7316
TITLE: Device Data Transfer
STATEMENT: >>>
The Patient needs the option to transfer the configuration, data, and records from an old device to a new device.
<<<

[USER_NEED]
UID: UN-7317
TITLE: Reset Data Preservation
STATEMENT: >>>
The Patient needs the device to preserve the configuration, data, and records after a factory reset.
<<<

[[/SECTION]]

[[SECTION]]
TITLE: Clinical Trials (Patient Experience)

[USER_NEED]
UID: UN-601
TITLE: Guided Trial Enrollment
STATEMENT: >>>
The Patient needs a secure, straightforward way to associate their account to one or more clinical trials that they are authorized to participate in. A Patient who is enrolled in a clinical trial is a Trial Participant.
<<<

[USER_NEED]
UID: UN-602
TITLE: Trial Schedule Default
STATEMENT: >>>
The Trial Participant needs the system to automatically apply the trial's medication protocol and configuration to their device schedule as a default.
<<<
RATIONALE: >>>
Simplify user onboarding but ultimately allow Patient to make further changes.
<<<

[USER_NEED]
UID: UN-603
TITLE: Trial Device Association
STATEMENT: >>>
The Trial Participant needs the system to associate a device with the clinical trial they are enrolled in.
<<<
RATIONALE: >>>
Ensures device data is shared with the correct clinical trial. Trial sponsor gives Trial Participant a device that is already associated with the clinical trial.
<<<

[USER_NEED]
UID: UN-7309
TITLE: Trial Participant Data Routing
STATEMENT: >>>
The Trial Participant needs the device to share data with only the clinical trial the device is associated with.
<<<
RATIONALE: >>>
A device in one trial shouldn't be submitting data to a trial it doesn't belong to.
<<<

[[/SECTION]]

[[SECTION]]
TITLE: Clinical Trials (Administrator Experience)

[[SECTION]]
TITLE: Setup & Collaboration

[USER_NEED]
UID: UN-7101
TITLE: Researcher Access
STATEMENT: >>>
A Clinical Researcher needs a secure environment to manage study settings, oversee participants, and review adherence data.
<<<

[USER_NEED]
UID: UN-7102
TITLE: Institutional Collaboration
STATEMENT: >>>
A Clinical Researcher needs to be able to work within an organizational structure where multiple team members can be associated with the same clinical site or institution.
<<<

[USER_NEED]
UID: UN-7103
TITLE: Secure Team Sharing
STATEMENT: >>>
Study owners need to grant other authorized researchers access to specific study dashboards and subject data to facilitate collaborative monitoring.
<<<

[[/SECTION]]

[[SECTION]]
TITLE: Protocol Definition & Participant Management

[USER_NEED]
UID: UN-7201
TITLE: Protocol Default Configuration
STATEMENT: >>>
The Researcher needs to be able to define a default medication schedule and device configuration that devices associated with the trial use when they are first set up.
<<<

[USER_NEED]
UID: UN-7202
TITLE: Participant Enrollment Authorization
STATEMENT: >>>
The Researcher needs the system to ensure only authorized trial participant Patient accounts are associated with the clinical trial.
<<<

[USER_NEED]
UID: UN-7203
TITLE: Participant Enrollment
STATEMENT: >>>
The Researcher needs to securely authorize a Trial Participant to associate their Patient account to the clinical trial.
<<<

[USER_NEED]
UID: UN-7305
TITLE: Participant Unique ID
STATEMENT: >>>
The Researcher needs to assign a unique identifier to each Trial Participant.
<<<
RATIONALE: >>>
Participants need to be identified with their investigator-defined Subject ID which serves as their pseudonymous identifier for the trial.
<<<

[USER_NEED]
UID: UN-7306
TITLE: Participant and Device Oversight
STATEMENT: >>>
The Researcher needs to access a list of all Trial Participants and devices associated with the trial, even if the device is not associated with a Patient or Trial Participant yet.
<<<

[USER_NEED]
UID: UN-7307
TITLE: Device Association
STATEMENT: >>>
The Researcher needs to be able to designate specific devices as only able to be associated with the trial.
<<<

[[/SECTION]]

[[SECTION]]
TITLE: Monitoring & Analytics

[USER_NEED]
UID: UN-7301
TITLE: Participant Adherence Monitoring
STATEMENT: >>>
The Researcher needs to monitor medication adherence records of all Trial Participants associated with the study.
<<<

[USER_NEED]
UID: UN-7302
TITLE: Data Access Control
STATEMENT: >>>
The Researcher needs the system to restrict access to only records and information they are duly authorized to access.
<<<

[USER_NEED]
UID: UN-7303
TITLE: Aggregate Compliance Insights
STATEMENT: >>>
The Researcher needs to view high-level adherence trends across all Trial Participants.
<<<

[USER_NEED]
UID: UN-7304
TITLE: Real-Time Data Accuracy
STATEMENT: >>>
The Researcher needs the system to differentiate between "known" dose events and "unknown" statuses (where a device has not checked in) to maintain the integrity of the clinical data set.
<<<

[USER_NEED]
UID: UN-7308
TITLE: Trial Data Intermixing Prevention
STATEMENT: >>>
The Researcher needs to access only data associated with the clinical trial.
<<<
RATIONALE: >>>
Prevent adherence data intermixing with other trials the Patient may be involved in, or a personally-owned device they have.
<<<

[[/SECTION]]

[[/SECTION]]

[[SECTION]]
TITLE: Stakeholder Requirements (Business & Regulatory)

[USER_NEED]
UID: UN-408
TITLE: Data Residency
STATEMENT: >>>
The System needs to comply with data residency laws that restrict geographically where the Patient data is stored.
<<<

[USER_NEED]
UID: UN-7310
TITLE: Scalability
STATEMENT: >>>
The System needs to support a minimum of 2,000 active concurrent users without errors or reliability issues.
<<<

[[/SECTION]]

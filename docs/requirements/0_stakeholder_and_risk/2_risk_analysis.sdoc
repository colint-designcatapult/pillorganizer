[DOCUMENT]
TITLE: ISO 14971 Risk Analysis / Hazard Traceability Matrix

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: TEXT
  FIELDS:
  - TITLE: UID
    TYPE: String
    REQUIRED: False
  - TITLE: STATEMENT
    TYPE: String
    REQUIRED: True
- TAG: HAZARD
  PROPERTIES:
    VIEW_STYLE: Narrative
  FIELDS:
  - TITLE: MID
    TYPE: String
    REQUIRED: False
  - TITLE: UID
    TYPE: String
    REQUIRED: True
  - TITLE: SEVERITY
    TYPE: SingleChoice(Catastrophic, Critical, Serious, Minor, Negligible)
    REQUIRED: True
  - TITLE: PROBABILITY
    TYPE: SingleChoice(Frequent, Probable, Occasional, Remote, Improbable)
    REQUIRED: True
  - TITLE: RISK_LEVEL
    TYPE: SingleChoice(Unacceptable, Conditional, Acceptable)
    REQUIRED: True
  - TITLE: RESIDUAL_SEVERITY
    TYPE: SingleChoice(Catastrophic, Critical, Serious, Minor, Negligible)
    REQUIRED: False
  - TITLE: RESIDUAL_PROBABILITY
    TYPE: SingleChoice(Frequent, Probable, Occasional, Remote, Improbable)
    REQUIRED: False
  - TITLE: RESIDUAL_RISK_LEVEL
    TYPE: SingleChoice(Unacceptable, Conditional, Acceptable)
    REQUIRED: False
  - TITLE: TITLE
    TYPE: String
    REQUIRED: True
  - TITLE: STATEMENT
    TYPE: String
    REQUIRED: True
  - TITLE: HARM
    TYPE: String
    REQUIRED: True
  - TITLE: ACCEPTANCE_JUSTIFICATION
    TYPE: String
    REQUIRED: False

[[SECTION]]
PREFIX: RISK-MED-
TITLE: Medication Hazards

[HAZARD]
UID: RISK-MED-1
SEVERITY: Critical
PROBABILITY: Occasional
RISK_LEVEL: Unacceptable
TITLE: Patient Overdose due to Incorrect Prompting of Medication
STATEMENT: >>>
The device experiences a logic error, memory corruption, or clock drift that causes it to illuminate an LED for a medication bin that is not yet due. The user relies on the cue and consumes an extra dose.
<<<
HARM: >>>
Drug toxicity leading to patient harm.
<<<

[HAZARD]
UID: RISK-MED-2
SEVERITY: Critical
PROBABILITY: Occasional
RISK_LEVEL: Unacceptable
TITLE: Missed Dose due to Failure to Prompt Medication
STATEMENT: >>>
The device fails to generate an alert at the scheduled time due to software lockup, logic failure, battery depletion, connectivity issues, or hardware failure. The user, relying on the device, assumes no medication is needed and misses the dose.
<<<
HARM: >>>
Therapeutic failure due to lack of medication.
<<<

[HAZARD]
UID: RISK-MED-3
SEVERITY: Serious
PROBABILITY: Probable
RISK_LEVEL: Unacceptable
TITLE: Operation with Stale or Unrecorded Data
STATEMENT: >>>
The device operates with a schedule that has not been synchronized for >24 hours (risk of schedule changes/clock drift) OR the device continues to operate when the internal memory is full (risk of overwriting compliance data).
<<<
HARM: >>>
Patient takes medication based on an old prescription that changed yesterday. Patient takes medication, but the device cannot record it. Doctor assumes non-compliance.
<<<

[HAZARD]
UID: RISK-MED-4
SEVERITY: Catastrophic
PROBABILITY: Probable
RISK_LEVEL: Unacceptable
TITLE: Device Confusion
STATEMENT: >>>
The patient possesses multiple devices and cannot differentiate between the device shown in the app and the physical device.
<<<
HARM: >>>
Patient takes medication from the wrong device.
<<<
ACCEPTANCE_JUSTIFICATION: >>>
TBD
<<<

[[/SECTION]]

[[SECTION]]
PREFIX: RISK-DATA-
TITLE: Data Integrity

[HAZARD]
UID: RISK-DATA-1
SEVERITY: Serious
PROBABILITY: Frequent
RISK_LEVEL: Unacceptable
TITLE: Data Corruption
STATEMENT: >>>
A software failure results in incorrect patient adherence data to be reported. (TBD)
<<<
HARM: >>>
TBD
<<<
ACCEPTANCE_JUSTIFICATION: >>>
Document in IFU that data is not to be used for medication management.
<<<

[HAZARD]
UID: RISK-DATA-2
SEVERITY: Critical
PROBABILITY: Frequent
RISK_LEVEL: Unacceptable
TITLE: Device Misattribution
STATEMENT: >>>
A software failure results in adherence data from one device to be presented to the user as if it were from another device.
<<<
HARM: >>>
TBD
<<<
ACCEPTANCE_JUSTIFICATION: >>>
TBD
<<<

[HAZARD]
UID: RISK-DATA-3
SEVERITY: Critical
PROBABILITY: Frequent
RISK_LEVEL: Unacceptable
TITLE: User Misattribution
STATEMENT: >>>
A software failure results in adherence data from one Patient to be presented to the user as if it were from another Patient.
<<<
HARM: >>>
TBD
<<<
ACCEPTANCE_JUSTIFICATION: >>>
TBD
<<<

[[/SECTION]]

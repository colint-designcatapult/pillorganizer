[DOCUMENT]
TITLE: ISO 14971 Risk Analysis / Hazard Traceability Matrix

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: TEXT
  FIELDS:
  - TITLE: UID
    TYPE: String
    REQUIRED: False
  - TITLE: STATEMENT
    TYPE: String
    REQUIRED: True
- TAG: HAZARD
  PROPERTIES:
    VIEW_STYLE: Narrative
  FIELDS:
  - TITLE: MID
    TYPE: String
    REQUIRED: False
  - TITLE: UID
    TYPE: String
    REQUIRED: False
  - TITLE: SEVERITY
    TYPE: SingleChoice(Catastrophic, Critical, Serious, Minor, Negligible)
    REQUIRED: True
  - TITLE: PROBABILITY
    TYPE: SingleChoice(Frequent, Probable, Occasional, Remote, Improbable)
    REQUIRED: True
  - TITLE: RISK_LEVEL
    TYPE: SingleChoice(Unacceptable, ALARP, Acceptable)
    REQUIRED: True
  - TITLE: TITLE
    TYPE: String
    REQUIRED: True
  - TITLE: STATEMENT
    TYPE: String
    REQUIRED: True
  - TITLE: HARM
    TYPE: String
    REQUIRED: True
  RELATIONS:
  - TYPE: Child
    ROLE: Mitigated_By

[[SECTION]]
PREFIX: RISK-MED-
TITLE: Medication Hazards

[HAZARD]
UID: RISK-MED-1
SEVERITY: Critical
PROBABILITY: Occasional
RISK_LEVEL: Unacceptable
TITLE: Patient Overdose due to Incorrect Prompting of Medication
STATEMENT: >>>
The device experiences a logic error, memory corruption, or clock drift that causes it to illuminate an LED for a medication bin that is not yet due. The user relies on the cue and consumes an extra dose.
<<<
HARM: >>>
Drug toxicity leading to patient harm.
<<<

[HAZARD]
UID: RISK-MED-2
SEVERITY: Critical
PROBABILITY: Occasional
RISK_LEVEL: Unacceptable
TITLE: Missed Dose due to Failure to Prompt Medication
STATEMENT: >>>
The device fails to generate an alert at the scheduled time due to software lockup, logic failure, battery depletion, connectivity issues, or hardware failure. The user, relying on the device, assumes no medication is needed and misses the dose.
<<<
HARM: >>>
Therapeutic failure due to lack of medication.
<<<

[HAZARD]
UID: RISK-MED-3
SEVERITY: Serious
PROBABILITY: Probable
RISK_LEVEL: Unacceptable
TITLE: Operation with Stale or Unrecorded Data
STATEMENT: >>>
The device operates with a schedule that has not been synchronized for >24 hours (risk of schedule changes/clock drift) OR the device continues to operate when the internal memory is full (risk of overwriting compliance data).
<<<
HARM: >>>
Patient takes medication based on an old prescription that changed yesterday. Patient takes medication, but the device cannot record it. Doctor assumes non-compliance.
<<<

[[/SECTION]]

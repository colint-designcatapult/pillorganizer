[DOCUMENT]
TITLE: SOUP List (Off-the-Shelf Software)

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: SOUP
  PROPERTIES:
    PREFIX: SOUP-
    VIEW_STYLE: Narrative
  FIELDS:
  - TITLE: MID
    TYPE: String
    REQUIRED: False
  - TITLE: UID
    TYPE: String
    REQUIRED: False
  - TITLE: TITLE
    TYPE: String
    REQUIRED: True
  - TITLE: VERSION
    TYPE: String
    REQUIRED: False
  - TITLE: MANUFACTURER
    TYPE: String
    REQUIRED: True
  - TITLE: PURPOSE
    TYPE: String
    REQUIRED: True
  - TITLE: KNOWN_BUGS
    TYPE: String
    REQUIRED: True
  - TITLE: RISK_ANALYSIS
    TYPE: String
    REQUIRED: True

[[SECTION]]
PREFIX: SOUP-FW-
TITLE: Firmware Dependencies

[SOUP]
UID: SOUP-FW-1
TITLE: platform-espressif32
VERSION: 6.3.2
MANUFACTURER: Espressif Systems & PlatformIO Labs (Open Source)
PURPOSE: Provides the REST API framework for the backend.
KNOWN_BUGS: Reviewed GitHub issues; no critical open bugs affect our use case.
RISK_ANALYSIS: >>>
TBD.
<<<

[[/SECTION]]

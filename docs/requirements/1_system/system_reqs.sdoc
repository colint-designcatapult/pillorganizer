[DOCUMENT]
TITLE: System Requirements Specification
PREFIX: SYS-REQ-

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: TEXT
  FIELDS:
  - TITLE: UID
    TYPE: String
    REQUIRED: False
  - TITLE: STATEMENT
    TYPE: String
    REQUIRED: True
- TAG: REQUIREMENT
  FIELDS:
  - TITLE: UID
    TYPE: String
    REQUIRED: True
  - TITLE: TITLE
    TYPE: String
    REQUIRED: True
  - TITLE: STATEMENT
    TYPE: String
    REQUIRED: True
  - TITLE: RATIONALE
    TYPE: String
    REQUIRED: False
  RELATIONS:
  - TYPE: Parent
    ROLE: Refines
  - TYPE: Parent
    ROLE: Mitigates

[[SECTION]]
TITLE: Device State & Operation

[[/SECTION]]

[[SECTION]]
TITLE: Central Backend Platform

[REQUIREMENT]
UID: SYS-REQ-11
TITLE: Central Backend Platform
STATEMENT: >>>
The system shall provide a Central Backend Platform to serve as the data aggregator and control plane to link the device to user applications (mobile app or web dashboard).
<<<
RELATIONS:
- TYPE: Parent
  VALUE: UN-402
  ROLE: Refines
- TYPE: Parent
  VALUE: UN-403
  ROLE: Refines

[REQUIREMENT]
UID: SYS-REQ-17
TITLE: Backend Scaling Capacity
STATEMENT: >>>
The Central Backend Platform shall support a minimum of 2,000 active concurrent users without errors or reliability issues.
<<<
RELATIONS:
- TYPE: Parent
  VALUE: UN-7310
  ROLE: Refines

[REQUIREMENT]
UID: SYS-REQ-16
TITLE: Backend Data Integrity
STATEMENT: >>>
The Central Backend Platform shall preserve and maintain all data stored in accordance with data retention requirements.
<<<
RELATIONS:
- TYPE: Parent
  VALUE: RISK-DATA-1
  ROLE: Mitigates
- TYPE: Parent
  VALUE: UN-405
  ROLE: Refines

[REQUIREMENT]
UID: SYS-REQ-10
TITLE: Backend Data Residency
STATEMENT: >>>
The Central Backend Platform, and user data processed and stored by it, shall be physically located in Canada.
<<<
RATIONALE: >>>
Client requirement.
<<<
RELATIONS:
- TYPE: Parent
  VALUE: UN-408
  ROLE: Refines

[REQUIREMENT]
UID: SYS-REQ-12
TITLE: Backend API Interface
STATEMENT: >>>
The Central Backend Platform shall provide a secure Application Programming Interface (API) to support requests from the device and user applications.
<<<
RELATIONS:
- TYPE: Parent
  VALUE: UN-202
  ROLE: Refines
- TYPE: Parent
  VALUE: UN-303
  ROLE: Refines
- TYPE: Parent
  VALUE: UN-405
  ROLE: Refines

[REQUIREMENT]
UID: SYS-REQ-13
TITLE: Backend Encryption
STATEMENT: >>>
The Central Backend Platform shall ensure all user data is encrypted in transit and in rest.
<<<

[REQUIREMENT]
UID: SYS-REQ-14
TITLE: Isolated Backend Environments
STATEMENT: >>>
The system shall allow for multiple, independent, and logically isolated Central Backend Platform environments to operate simultaneously. Each such independent environment is a Tenant.
<<<
RATIONALE: >>>
Allows separate/isolated production, staging, and testing environments along with an isolated instance for each clinical trial.
<<<
RELATIONS:
- TYPE: Parent
  VALUE: RISK-DATA-1
  ROLE: Mitigates
- TYPE: Parent
  VALUE: UN-7308
  ROLE: Refines

[REQUIREMENT]
UID: SYS-REQ-15
TITLE: Backend Environment Routing
STATEMENT: >>>
The system shall provide a mechanism such that the device and the user applications are routed to the proper Tenant.
<<<
RATIONALE: >>>
If we have multiple environments, we need a way to point the device/apps to the current one.
<<<
RELATIONS:
- TYPE: Parent
  VALUE: UN-7309
  ROLE: Refines
- TYPE: Parent
  VALUE: RISK-DATA-1
  ROLE: Mitigates

[REQUIREMENT]
UID: SYS-REQ-38
TITLE: Secure Tenant Coordination
STATEMENT: >>>
The system shall provide a secure mechanism for a Tenant to share explicitly designated shared state between other Tenants.
<<<
RELATIONS:
- TYPE: Parent
  VALUE: UN-7309
  ROLE: Refines
- TYPE: Parent
  VALUE: UN-7314
  ROLE: Refines

[[SECTION]]
TITLE: Authentication & Accounts

[REQUIREMENT]
UID: SYS-REQ-21
TITLE: User Account Creation
STATEMENT: >>>
The system shall allow a patient or caregiver to create an account using secure credentials to uniquely identify the user.
<<<
RELATIONS:
- TYPE: Parent
  VALUE: UN-301
  ROLE: Refines
- TYPE: Parent
  VALUE: UN-302
  ROLE: Refines

[REQUIREMENT]
UID: SYS-REQ-22
TITLE: Account Unique Identifier
STATEMENT: >>>
Every user account shall be assigned a unique, global, and permanent user identifier (user ID) that 1-to-1 maps to a user account.
<<<
RELATIONS:
- TYPE: Parent
  VALUE: UN-301
  ROLE: Refines
- TYPE: Parent
  VALUE: UN-302
  ROLE: Refines

[REQUIREMENT]
UID: SYS-REQ-23
TITLE: User Account Login
STATEMENT: >>>
The system shall allow a user to securely log in to their account using previously established user credentials, granting them a temporary session to authenticate user application requests with.
<<<
RELATIONS:
- TYPE: Parent
  VALUE: UN-306
  ROLE: Refines
- TYPE: Parent
  VALUE: UN-7311
  ROLE: Refines

[REQUIREMENT]
UID: SYS-REQ-24
TITLE: Global User Accounts
STATEMENT: >>>
The system shall allow a single patient or caregiver account to be used with all devices and tenants the user has authorized access to.
<<<
RATIONALE: >>>
Single sign-on for tenants.
<<<
RELATIONS:
- TYPE: Parent
  VALUE: UN-601
  ROLE: Refines
- TYPE: Parent
  VALUE: UN-501
  ROLE: Refines

[REQUIREMENT]
UID: SYS-REQ-25
TITLE: User Account Name
STATEMENT: >>>
The system shall allow authenticated users to view and modify their own display name that may be displayed to other users.
<<<
RELATIONS:
- TYPE: Parent
  VALUE: UN-7312
  ROLE: Refines

[REQUIREMENT]
UID: SYS-REQ-18
TITLE: Backend Authentication Requirement
STATEMENT: >>>
The system shall require authentication for all inbound device and user application requests to the Central Backend Platform, attributable to a specific user or device, with the sole exception of explicitly documented public endpoints (e.g., health checks, initial authentication).
<<<
RELATIONS:
- TYPE: Parent
  VALUE: UN-7311
  ROLE: Refines

[REQUIREMENT]
UID: SYS-REQ-19
TITLE: Backend Device Authorization
STATEMENT: >>>
The system shall require all authenticated inbound device requests to the Central Backend Platform to be authorized for that specific device.
<<<
RELATIONS:
- TYPE: Parent
  VALUE: RISK-DATA-2
  ROLE: Refines

[[/SECTION]]

[[/SECTION]]

[[SECTION]]
TITLE: Device Identity

[REQUIREMENT]
UID: SYS-REQ-36
TITLE: Device List
STATEMENT: >>>
The system shall allow the user to view a list of all devices they posses or have authorized access to by device nickname.
<<<
RELATIONS:
- TYPE: Parent
  VALUE: UN-7314
  ROLE: Refines
- TYPE: Parent
  VALUE: UN-7313
  ROLE: Refines

[REQUIREMENT]
UID: SYS-REQ-37
TITLE: Device Switch
STATEMENT: >>>
The system shall allow a user to switch which device they are accessing or modifying device state, configuration, or records for, amongst the devices they have authorized access to.
<<<
RELATIONS:
- TYPE: Parent
  VALUE: UN-7314
  ROLE: Refines

[REQUIREMENT]
UID: SYS-REQ-26
TITLE: Device Nickname
STATEMENT: >>>
The system shall allow the user to view and modify a nickname for the device.
<<<
RELATIONS:
- TYPE: Parent
  VALUE: UN-7313
  ROLE: Refines

[REQUIREMENT]
UID: SYS-REQ-27
TITLE: Device Nickname Display
STATEMENT: >>>
The system shall display the Device Nickname while viewing device state, making configuration changes, viewing adherence records, or in mobile app notifications.
<<<
RELATIONS:
- TYPE: Parent
  VALUE: RISK-MED-4
  ROLE: Mitigates

[REQUIREMENT]
UID: SYS-REQ-39
TITLE: Device Serial Number
STATEMENT: >>>
The system shall identify a specific physical device with a permanent, unique serial number.
<<<
RELATIONS:
- TYPE: Parent
  VALUE: UN-7313
  ROLE: Refines

[REQUIREMENT]
UID: SYS-REQ-40
TITLE: Device Serial Number Display
STATEMENT: >>>
The system shall display the serial n
<<<
RELATIONS:
- TYPE: Parent
  VALUE: UN-7313
  ROLE: Refines

[REQUIREMENT]
UID: SYS-REQ-41
TITLE: Device Logical Identifier
STATEMENT: >>>
The system shall assign a globally unique identifier, other than the serial number, that identifies a single physical device.
<<<
RELATIONS:
- TYPE: Parent
  VALUE: UN-7315
  ROLE: Refines

[[/SECTION]]

[[SECTION]]
TITLE: Device Configuration

[REQUIREMENT]
UID: SYS-REQ-28
TITLE: Device Primary User
STATEMENT: >>>
The device shall be associated with exactly one primary user account designated as the Primary User of the device.
<<<
RATIONALE: >>>
Should never be no primary user (doesn't make sense) and should never have more than one for risk mitigation.
<<<
RELATIONS:
- TYPE: Parent
  VALUE: UN-307
  ROLE: Refines

[REQUIREMENT]
UID: SYS-REQ-30
TITLE: Primary User Transfer
STATEMENT: >>>
The system shall allow a Primary User to transfer the Primary User status to another user account, and in doing so, removing their own Primary User status.
<<<
RELATIONS:
- TYPE: Parent
  VALUE: UN-503
  ROLE: Refines
- TYPE: Parent
  VALUE: UN-504
  ROLE: Refines

[REQUIREMENT]
UID: SYS-REQ-31
TITLE: Caregiver Access
STATEMENT: >>>
The system shall allow the Primary User to designate another user account as a Caregiver for the device.
<<<
RELATIONS:
- TYPE: Parent
  VALUE: UN-303
  ROLE: Refines

[REQUIREMENT]
UID: SYS-REQ-32
TITLE: Caregiver Monitoring
STATEMENT: >>>
The system shall allow the Caregiver to view the device state, adherence records, and configuration, and mobile notifications.
<<<
RELATIONS:
- TYPE: Parent
  VALUE: UN-303
  ROLE: Refines

[REQUIREMENT]
UID: SYS-REQ-33
TITLE: Caregiver Read-Access Only
STATEMENT: >>>
The system shall deny the Caregiver access to make changes to device configuration, state, or records.
<<<
RELATIONS:
- TYPE: Parent
  VALUE: UN-307
  ROLE: Refines

[REQUIREMENT]
UID: SYS-REQ-34
TITLE: Caregiver List
STATEMENT: >>>
The system shall allow the Primary User to view the list of Caregivers authorized access to the device, and their Account Names.
<<<
RELATIONS:
- TYPE: Parent
  VALUE: UN-304
  ROLE: Refines
- TYPE: Parent
  VALUE: UN-7312
  ROLE: Refines

[REQUIREMENT]
UID: SYS-REQ-35
TITLE: Caregiver Revocation
STATEMENT: >>>
The system shall allow the Primary User to revoke Caregiver access to the device for a specific Caregiver account.
<<<
RELATIONS:
- TYPE: Parent
  VALUE: UN-304
  ROLE: Refines

[[SECTION]]
TITLE: Device Provisioning

[REQUIREMENT]
UID: SYS-REQ-42
TITLE: Device Provisioning
STATEMENT: >>>
The system shall provide a mechanism for the user to program Wi-Fi credentials on the device for the device to access the Central Backend Platform. The process of securely programming Wi-Fi credentials and linking the device to the user account is called provisioning.
<<<
RELATIONS:
- TYPE: Parent
  VALUE: UN-501
  ROLE: Refines

[REQUIREMENT]
UID: SYS-REQ-29
TITLE: Initial Primary User
STATEMENT: >>>
The system shall designate the user account that provisioned the device as the primary user of the device after provisioning if no explicit alternative Primary User is designated.
<<<
RATIONALE: >>>
Sane default, prevents device from not having a primary user.
<<<
RELATIONS:
- TYPE: Parent
  VALUE: UN-503
  ROLE: Refines
- TYPE: Parent
  VALUE: UN-501
  ROLE: Refines

[REQUIREMENT]
UID: SYS-REQ-43
TITLE: In-App Provisioning
STATEMENT: >>>
The system shall allow the user provision the device via the mobile application.
<<<
RELATIONS:
- TYPE: Parent
  VALUE: UN-501
  ROLE: Refines

[REQUIREMENT]
UID: SYS-REQ-44
TITLE: Provisioning Security
STATEMENT: >>>
The system shall ensure that a device provisioning is only authorized by the user in physical possession of the device.
<<<
RELATIONS:
- TYPE: Parent
  VALUE: UN-7311
  ROLE: Refines

[REQUIREMENT]
UID: SYS-REQ-45
TITLE: Existing Device Provisioning
STATEMENT: >>>
The system shall allow a primary user to re-provision an existing device, preserving its configuration, data, and records.
<<<
RELATIONS:
- TYPE: Parent
  VALUE: UN-7317
  ROLE: Refines

[REQUIREMENT]
UID: SYS-REQ-46
TITLE: Device Transfer Provisioning
STATEMENT: >>>
The system shall allow a primary user to provision a new device and optionally transfer the configuration, data, and records from an existing device they are the primary user of.
<<<
RELATIONS:
- TYPE: Parent
  VALUE: UN-7316
  ROLE: Refines

[REQUIREMENT]
UID: SYS-REQ-47
TITLE: Provisioning Credentials
STATEMENT: >>>
The system shall grant a device unique, secure credentials during provisioning to authenticate with the Central Backend Platform.
<<<
RELATIONS:
- TYPE: Parent
  VALUE: UN-7311
  ROLE: Refines

[REQUIREMENT]
UID: SYS-REQ-48
TITLE: Provisioning Credentials Revocation
STATEMENT: >>>
The system shall ensure that previously issued device credentials are revoked when the device is provisioned.
<<<
RELATIONS:
- TYPE: Parent
  VALUE: UN-7311
  ROLE: Refines
- TYPE: Parent
  VALUE: UN-502
  ROLE: Refines

[[/SECTION]]

[[/SECTION]]

[[SECTION]]
TITLE: Remote Data Synchronization

[REQUIREMENT]
UID: SYS-REQ-7
TITLE: Synchronization Interface
STATEMENT: >>>
The device shall provide a bi-directional interface to synchronize schedule, state, and adherence data with the Central Backend Platform.
<<<
RATIONALE: >>>
Allows the patient, clinicians, and caretakers to remotely monitor compliance, update medication scheduling/configuration, and view device status.
<<<

[REQUIREMENT]
UID: SYS-REQ-6
TITLE: Periodic Device Synchronization
STATEMENT: >>>
The device shall synchronize with the Central Backend Platform on a 15-minute interval to check for changes to the device configuration and schedule.
<<<
RATIONALE: >>>
Ensures changes to configuration or schedule by the user are applied to the device in a timely manner. Interval avoids battery drain of constant device connection.
<<<

[REQUIREMENT]
UID: SYS-REQ-8
TITLE: Synchronization on State Change
STATEMENT: >>>
The device shall synchronize with the Central Backend Platform within 5 seconds of a bin state change on the device.
<<<
RATIONALE: >>>
Ensures remote users have a "live" view of the device state.
<<<

[REQUIREMENT]
UID: SYS-REQ-9
TITLE: Synchronization Failure Handling
STATEMENT: >>>
The device shall re-attempt synchronization with the Central Backend Platform in the event a previous synchronization attempt fails for any reason (including connectivity or errors). The re-attempt shall use exponential backoff. When the exponential backoff timer exceeds 15 minutes, the re-attempt is cancelled.
<<<
RATIONALE: >>>
Attempt re-synchronization very soon after to work around intermittent connectivity issues, and delay further re-attempts as a rate limiting and power saving measure. When the exponential backoff reaches 15 minutes, fall back to [SYS-REQ-6] periodic device sync.
<<<

[[/SECTION]]

[[SECTION]]
TITLE: Offline and Fail-Safe Operation

[REQUIREMENT]
UID: SYS-REQ-1
TITLE: Device Offline Autonomous Operation
STATEMENT: >>>
When synchronization with an Authorized Host System is not possible (e.g., disconnected from Wi-Fi/Bluetooth, outages, or errors), the device shall continue to execute the currently loaded medication schedule, trigger visual alerts, and log user interactions (bin openings) to local memory.
<<<
RATIONALE: >>>
Ensures patient safety and adherence tracking are not interrupted by connectivity failures.
<<<
RELATIONS:
- TYPE: Parent
  VALUE: RISK-MED-2
  ROLE: Mitigates

[REQUIREMENT]
UID: SYS-REQ-2
TITLE: Definition of Safe State
STATEMENT: >>>
When the system determines it can no longer operate reliably, it shall enter the "Safe State." In this state:
1.) All scheduled medication alerts are disabled (no "Take Pill" lights).
2.) The device shall display a distinct "Service Required" visual pattern (e.g., All LEDs blinking Yellow at 0.5Hz).
3.) Medication adherence recording is disabled.
<<<
RELATIONS:
- TYPE: Parent
  VALUE: RISK-MED-3
  ROLE: Mitigates

[REQUIREMENT]
UID: SYS-REQ-3
TITLE: Extended Offline Lockout
STATEMENT: >>>
If the device has not successfully synchronized to an Authorized Host System for more than 24 hours, it shall transition to the Safe State.
<<<
RATIONALE: >>>
Ensures the Real-Time Clock (RTC) has been re-synchronized and the schedule is fresh.
<<<
RELATIONS:
- TYPE: Parent
  VALUE: RISK-MED-3
  ROLE: Mitigates

[REQUIREMENT]
UID: SYS-REQ-4
TITLE: Audit Log Saturation Lockout
STATEMENT: >>>
If the non-volatile memory reserved for the Event Log reaches 95% capacity (or less than 10 events remaining), the device shall transition to the Safe State.
<<<
RATIONALE: >>>
Prevents the overwrite of critical medical history data. It is unlikely this condition would be met before the "extended offline" lockout.
<<<
RELATIONS:
- TYPE: Parent
  VALUE: RISK-MED-3
  ROLE: Mitigates

[REQUIREMENT]
UID: SYS-REQ-5
TITLE: Safe State Recovery
STATEMENT: >>>
The device shall only exit the Safe State and resume normal operation upon a successful data sync to an Authorized Host System.
<<<
RELATIONS:
- TYPE: Parent
  VALUE: RISK-MED-3
  ROLE: Mitigates

[[/SECTION]]

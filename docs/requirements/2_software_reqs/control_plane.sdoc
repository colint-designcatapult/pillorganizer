[DOCUMENT]
TITLE: Global Control Plane Requirements Specification (SRS)
PREFIX: CTRL-REQ-

[[SECTION]]
TITLE: Global Users & Device Provisioning Service

[REQUIREMENT]
UID: CTRL-REQ-1
TITLE: Application Programming Interface
STATEMENT: >>>
The control plane shall expose an API to serve requests from the device and user applications. This interface is called the Global Users & Device Provisioning Service.
<<<
RELATIONS:
- TYPE: Parent
  VALUE: SYS-REQ-11

[REQUIREMENT]
UID: CTRL-REQ-2
TITLE: API Device Authentication
STATEMENT: >>>
The control plane shall ensure all API requests from the device, except those explicitly designated as public, are authenticated as originating from the device using a combination of device ID, serial number, and shared secret.
<<<
RELATIONS:
- TYPE: Parent
  VALUE: SYS-REQ-18

[REQUIREMENT]
UID: CTRL-REQ-3
TITLE: API User Authentication
STATEMENT: >>>
The control plane shall ensure all API requests from user applications, except those explicitly designated as public, are authenticated and attributable to a specific user account.
<<<
RELATIONS:
- TYPE: Parent
  VALUE: SYS-REQ-18

[REQUIREMENT]
UID: CTRL-REQ-8
TITLE: Internal API
STATEMENT: >>>
The control plane shall define and expose an API for Tenants to communicate with the control plane, and for the control plane to communicate with Tenants. This API is called the Internal API.
<<<
RELATIONS:
- TYPE: Parent
  VALUE: SYS-REQ-38

[REQUIREMENT]
UID: CTRL-REQ-9
TITLE: Internal API Security
STATEMENT: >>>
The control plane shall require all requests from the Tenant via the Internal API are authenticated as originating from a legitimate Tenant instance.
<<<
RELATIONS:
- TYPE: Parent
  VALUE: SYS-REQ-38

[REQUIREMENT]
UID: CTRL-REQ-10
TITLE: Internal API Request Authentication
STATEMENT: >>>
The control plane shall authenticate requests to the Tenant via the Internal API in a way that asserts that the request originated from the control plane.
<<<
RELATIONS:
- TYPE: Parent
  VALUE: SYS-REQ-38

[[/SECTION]]

[[SECTION]]
TITLE: User Profile & Management

[REQUIREMENT]
UID: CTRL-REQ-4
TITLE: User Identifier Creation
STATEMENT: >>>
The control plane shall create a User profile record and assign a unique user identifier to the account when a user account is created.
<<<
RELATIONS:
- TYPE: Parent
  VALUE: SYS-REQ-22

[REQUIREMENT]
UID: CTRL-REQ-5
TITLE: User Profile
STATEMENT: >>>
The control plane shall act as the single source of truth for the user profile record.
<<<
RELATIONS:
- TYPE: Parent
  VALUE: SYS-REQ-22

[REQUIREMENT]
UID: CTRL-REQ-6
TITLE: User Display Name
STATEMENT: >>>
The control plane shall provide an API for a user to view and update their display name.
<<<
RELATIONS:
- TYPE: Parent
  VALUE: SYS-REQ-25

[REQUIREMENT]
UID: CTRL-REQ-7
TITLE: User Identifier Use
STATEMENT: >>>
The control plane shall identify users in the internal API by user identifier.
<<<
RELATIONS:
- TYPE: Parent
  VALUE: SYS-REQ-22

[[/SECTION]]

[[SECTION]]
TITLE: User Device Access

[REQUIREMENT]
UID: CTRL-REQ-11
TITLE: User Devices List API
STATEMENT: >>>
The control plane shall provide an API to allow a user to view the devices they have access to, their level of access, the nickname of the device, and the connection information to the Tenant's Central Backend Platform.
<<<
RELATIONS:
- TYPE: Parent
  VALUE: SYS-REQ-36
- TYPE: Parent
  VALUE: SYS-REQ-15

[REQUIREMENT]
UID: CTRL-REQ-13
TITLE: User Devices List API Cache
STATEMENT: >>>
The control plane shall source the user-devices access list from Tenants using the Internal API.
<<<
RATIONALE: >>>
The user device list at the control plane layer is basically a cache. Tenants maintain source of truth for device access.
<<<

[[/SECTION]]

[[SECTION]]
TITLE: Tenant Routing

[REQUIREMENT]
UID: CTRL-REQ-16
TITLE: Device Tenant Assignment
STATEMENT: >>>
The control plane shall maintain the authoritative record of which tenant a device belongs to.
<<<
RELATIONS:
- TYPE: Parent
  VALUE: SYS-REQ-15

[REQUIREMENT]
UID: CTRL-REQ-15
TITLE: Device-Tenant Routing
STATEMENT: >>>
The control plane shall provide an API for the device or user application to look up the connection information for the Central Backend Platform that the device belongs to.
<<<
RELATIONS:
- TYPE: Parent
  VALUE: SYS-REQ-15

[[/SECTION]]

[[SECTION]]
TITLE: Device Provisioning

[REQUIREMENT]
UID: CTRL-REQ-17
TITLE: Provision Claim Initiation
STATEMENT: >>>
The control plane shall provide an API for the user application to initiate provisioning of a device.
<<<
RELATIONS:
- TYPE: Parent
  VALUE: SYS-REQ-43

[REQUIREMENT]
UID: CTRL-REQ-18
TITLE: Provision Claim Parameters
STATEMENT: >>>
The control plane claim initiation API shall accept a serial number and an optional existing logical device ID.
<<<
RELATIONS:
- TYPE: Parent
  VALUE: SYS-REQ-46
- TYPE: Parent
  VALUE: SYS-REQ-45

[REQUIREMENT]
UID: CTRL-REQ-19
TITLE: Provision Claim Device Access
STATEMENT: >>>
The control plane claim initiation API shall ensure, when an existing logical device ID is specified, that the user is the primary owner of the existing device and that the existing device exists.
<<<
RELATIONS:
- TYPE: Parent
  VALUE: SYS-REQ-47
- TYPE: Parent
  VALUE: SYS-REQ-44

[REQUIREMENT]
UID: CTRL-REQ-20
TITLE: Provision Claim Token
STATEMENT: >>>
The control plane initiation API shall, after duly authorizing the request, generate temporary credentials for the device to securely identify itself with.
<<<
RELATIONS:
- TYPE: Parent
  VALUE: SYS-REQ-47
- TYPE: Parent
  VALUE: SYS-REQ-44
- TYPE: Parent
  VALUE: IC-15

[REQUIREMENT]
UID: CTRL-REQ-21
TITLE: Provision Claim Token Expiration
STATEMENT: >>>
The control plane initiation API shall ensure that a provision claim credential can only be used for a period of ten (10) minutes after issuance.
<<<
RELATIONS:
- TYPE: Parent
  VALUE: SYS-REQ-47
- TYPE: Parent
  VALUE: SYS-REQ-44

[REQUIREMENT]
UID: CTRL-REQ-22
TITLE: Provision Claim Certificate API
STATEMENT: >>>
The control plane shall provide an API for the device to present its serial number and a claim credential receive a temporary claim certificate. The temporary claim certificate shall be used to authenticate with IoT Core Fleet Provisioning.
<<<
RELATIONS:
- TYPE: Parent
  VALUE: SYS-REQ-47
- TYPE: Parent
  VALUE: SYS-REQ-44
- TYPE: Parent
  VALUE: IC-18

[REQUIREMENT]
UID: CTRL-REQ-23
TITLE: Provision Claim Certificate Security
STATEMENT: >>>
The control plane shall claim certificate API shall ensure the validity of presented claim credentials.
<<<
RELATIONS:
- TYPE: Parent
  VALUE: SYS-REQ-44

[REQUIREMENT]
UID: CTRL-REQ-24
TITLE: Provision Claim Certificate Expiration
STATEMENT: >>>
The control plane shall claim certificate API shall ensure the temporary claim certificate can only be used for a period of five (5) minutes after issuance.
<<<
RELATIONS:
- TYPE: Parent
  VALUE: SYS-REQ-47
- TYPE: Parent
  VALUE: SYS-REQ-44

[REQUIREMENT]
UID: CTRL-REQ-25
TITLE: Fleet Provision Hook
STATEMENT: >>>
The control plane shall receive requests from the device for permanent certificates via IoT Core Fleet Provisioning and generate them if authorized.
<<<
RELATIONS:
- TYPE: Parent
  VALUE: SYS-REQ-47
- TYPE: Parent
  VALUE: SYS-REQ-44
- TYPE: Parent
  VALUE: IC-17

[REQUIREMENT]
UID: CTRL-REQ-26
TITLE: Fleet Provision Hook Validation
STATEMENT: >>>
The control plane receive validate requests and only issue permanent certificates to devices authorized by serial number, claim identifier, and claim token.
<<<
RELATIONS:
- TYPE: Parent
  VALUE: SYS-REQ-47
- TYPE: Parent
  VALUE: SYS-REQ-44
- TYPE: Parent
  VALUE: IC-18

[REQUIREMENT]
UID: CTRL-REQ-27
TITLE: Provision Tenant Assignment
STATEMENT: >>>
The control plane shall ensure that once a device is provisioned, its communications, configuration, and data flow exclusively through exclusively the Tenant the device is assigned to.
<<<
RELATIONS:
- TYPE: Parent
  VALUE: SYS-REQ-38
- TYPE: Parent
  VALUE: SYS-REQ-14

[[/SECTION]]
